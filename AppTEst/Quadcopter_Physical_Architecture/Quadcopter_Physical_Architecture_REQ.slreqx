# Quadcopter_Physical_Architecture_REQ

## 9: Physical Requirements (Functional)

### 9.1: Weight (Functional)
The quadcopter weight shall not exceed 10 kg.

### 9.4: Motors (Functional)
The quadcopter shall have four independent motors.

### 9.2: Cost (Functional)
The quadcopter cost shall not exceed $1000 USD.

### 9.3: Power (Functional)
The quadcopter shall be battery powered.

## 10: Performance (Functional)
Performance Requirements

### 10.1: Hover (Functional)
The quadcopter shall be able to hover for 10 minutes at normal power draw.

## 11: Communications (Functional)
Communications Requirements

### #9: WiFi (Functional)
The quadcopter shall interface with the ground station using a WiFi radio.

### 11.1: RF (Functional)
The quadcopter shall interface with the ground station using an RF radio.

### 11.2: 4G (Functional)
The quadcopter shall interface with the ground station using a 4G radio.

## 12: Payload (Functional)
Payload Requirements

### 12.1: Camera (Functional)
The quadcopter shall have a visual sensor.

### 12.2: Video Feed (Functional)
The quadcopter shall use the communication system to stream its video feed to the ground station.
