# SkyzerMissionModel_REQ

## 1.1.4: The system shall provide Ground Control to perform various communication capabilities that will support search and rescue efforts during search and rescue missions (Functional)

### 1.1.4.1: DELETED ... Out of Scope (Functional)

## 1.1.3: The system shall provide a surveillance capabilities to support search and rescue missions (Functional)

### 1.1.3.1: The system shall use UAV to locate people during search and rescue missions with use of payloads, full motion video (Functional)

## 1.1.2: The system shall perform various imaging capabilities for search and rescue (Functional)

### 1.1.2.1: Ground Control to have image-processing capabilities to support identifying locations, lost personnel, and drop locations for search and rescue (Functional)

### 1.1.2.2: Ground Control to have image-exploitation capabilities to support imagery mapping and seeking capabilities (Functional)

## 1.1.1: The system shall provide UAV capability that will support search and rescue missions (Functional)

### 1.1.1.4: The system shall provide UAV to have autonomous shipboard launch and Recover with little or no human interfacing (Functional)

#### 1.1.1.4.2: The system shall to be able to Launch and Recover in sea states five without causing damage to the UAV, ship or crew. (Functional)

#### 1.1.1.4.1: The system shall able to launch and land off of a Arleigh Burke Class Destroyers (Functional)

### 1.1.1.5: The system shall maintain position, hover over an area of interest (Functional)

### 1.1.1.1: The system shall fly a predetermined pattern in order to conduct search and rescue reconnaissance with either IR sensors or full motion video (Functional)

### 1.1.1.2: The system shall conduct a maximum of 5 hours of operations for search and rescue missions without refueling (Functional)

### 1.1.1.3: The system shall be able to follow a flight path even if it loses connection with ship’s ground control station (Functional)

### 1.1.1.6: The system shall transmission bandwidth for communication with the ground control station will be able to transmit full motion video (Functional)

## SMNeed_2: There is a mission capability need that will perform various imaging capabilities for search and rescue missions. (Functional)

### SMNeed_2.1: There is a mission capability need that will improved image-processing capabilities to support identifying locations, lost personnel and/or drop location for search and rescue mission (Functional)

## SMNeed_3: There is mission capability need that will provide UAV capacity for supporting search and rescue missions. (Functional)

### SMNeed_3.4: The mission will provide capability to have autonomous ship board landing (Functional)

### SMNeed_3.8: The mission will need to finding People during the search and rescue mission via any of the following payloads, deployable mission payload not less than 200 lbs total in four individually deployable segments 50 lb or less. (Functional)

### SMNeed_3.7: The mission will need to launch and recover the UAV in sea state five without causing damage to the UAV, ship and crew. (Functional)

### SMNeed_3.6: The UAV will to be able to be launch and land off of a Arleigh Burke Class Destroyers (Functional)

### SMNeed_3.2: There is a mission capability that will need a UAV to conduct a max of 5 hour operations for search and rescue missions without refueling (Functional)

### SMNeed_3.3: The mission will need the UAV to still be able to follow flight path even if UAV loses connection with Ship Ground station (Functional)

### SMNeed_3.5: The mission will need for the UAV transmission bandwidth for communication with ground station shall be able to transmit full motion video (Functional)

### SMNeed_3.1: The mission will provide a UAV to fly a predetermine pattern (Functional)

### SMNeed_3.9: The mission will need to be operational in Sea State 7 conditions with wind aloft not less than 80 knots. (Functional)

## SMNeed_5: The mission system will need to have a minimum of Category 2 Airworthiness IAW NAVAIRINST 13034.1D (Functional)

## SMNeed_4: There is a mission will constraint to use the standard architecture for developing the UAS Control Segment for ground station implementation. "UAS Control Segment (UCS) Architecture Model Implementation Reference Version 2.3" (Functional)
