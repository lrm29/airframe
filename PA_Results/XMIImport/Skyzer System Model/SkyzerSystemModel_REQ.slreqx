# SkyzerSystemModel_REQ

## 868 (Functional)

### 868.2: The amplitude shall be reduced to 1/3 or less of the original disturbance. (Functional)

### 868.5: The damping requirement applies to all initial displacements of the landing gear under the following conditions: all permissible gross weights, centers of gravity, and ground speeds on any paved surface with critical components worn to the maximum allowable. (Functional)

### 868.4: The exceptions shall include brake squeal and chatter. (Functional)

### 868.3: The amplitude shall be reduced to the required amount after 3 cycles. (Functional)

### 868.1: The landing gear shall have natural or augmented damping. (Functional)

## 772: Reversal of the landing gear control during actuation shall result in the landing gear going to the last position selected. (Functional)

## 900: The (TBS) . types of landing gear servicing shall be accomplished without removal of components or jacking of the complete air vehicle. (Functional)

## 899: Where joints and wear surfaces are required, they shall accommodate repairability by (TBS) . (Functional)

## 891: Emergency ground directional control provided by the landing gear, if required, shall be provided with the following characteristics: (TBS). (Functional)

## 1294: 1.0 Preform Data Collection This step involves gathering the basic upfront documentation for the program. It also involves setting up the base model. Input: CDD, ICD, AoA,4.0M Data, White Papers, etc. Output: Organized data, model set-up (Functional)

### 1294.1: This step involves identifying any previous documentation or prior work that has been completed that can serve as a point of reference. Input: Initial Capabilities Document (ICD), Capability Development Document (CDD), AoA, POM Issue sheet, 4.0M analysis (ICTB3) CONOPS, CBA, As-Is information, fleet input, NARG priorities list, Design Reference Missions (OPSIT/TACSIT), Deployment Debriefs, ROC/POE, market research, white papers, deficiency reports, obsolescence issues, etc. (Functional)

### 1294.2: Assess early inputs for sufficiency/completeness and identify gaps Assess what data is stable and what will not change and can potentially begin being modeled. ex Interface Control Document Assess data set for missing data (Functional)

### 1294.3: Setting up the base model - configuring the starter model(s), leveraging integrated dictionary, identifying design patterns/etc., constructing digital sign-off mechanism, identifying needed libraries, tailoring enterprise modeling standards/style guide/modeling best practices for specific program use. (Functional)

## 1295: 2.0 Analyze Stakeholder Needs Purpose • Performing this activity captures the provided stakeholder requirements in the model by specifying the mission level requirements that must be satisfied and sets the context for the system(s) needed to solve the problem. Input • As-is system (and SoS) details • CONOPS • Integrated Capability Framework (ICF) details (ICTB 3) • Initial Capabilities Document (ICD) / Capability Development Document (CDD) • Enterprise use cases • Measures of effectiveness (MOE) Output • Characterization of system and operational context • Model(s) of Operational requirements and To-be domain References: [1] Section 6.4.1 Business or Mission Analysis Process [2] Section 6.4.1 Business or Mission Analysis Process [3] Section 17.3.2 Analyze Stakeholder Needs (pg. 431) [4] Chapter 6 Analyze Mission and Stakeholder Needs (pg. 39) (Functional)

### 1295.1: Purpose: Define the existing, as-is system which includes further refinement of the problem space, system boundary,Initial Operational View, and early characterization of reusable components. Outputs: Model of existing system and its limitations. Modeling sufficient to identify current limitations and what you want to carry into To Be environment (Functional)

### 1295.2: Purpose: Model the provided CDD Output: CDD in a model (Functional)

### 1295.3: Purpose: Model provided Operational Context consisting of CONOPS, DRMs, etc. (Functional)

### 1295.4: Purpose: Define the top level context for the to-be domain accounting for correction of current system limitations and as-is components to be included in the to-be system. Include DRMs not provided via Mission Engineering (Logistics, Training, Environmental etc). (Functional)

### 1295.5: N/A (Functional)

### 1295.6: Purpose: A validation review with the operational stakeholders that the model is a correct representation of the input documents. ex. CDD, DRM. (Functional)

## 1296: 3.0 Analyze Item (Black Box) Requirements Summary For the level of the system currently being analyzed, this activity specifies the requirements for the items(s) as a black box in terms of its input and output behavior and other externally observable characteristics. This step should be repeated as work progresses through each level of the system (e.g. system, sub-system, set, etc.). The Mission, Operational, Logistics and Environmental Design Reference Missions (or their subsets) describe how the item interacts with the external systems and identified users to achieve the mission objectives. Input • Project constraints • Life cycle sustainment strategy • Problem or opportunity statement • Mission requirements • CDD • MOEs • Integrated capability technical baseline (ICTB) allocated system performance Output • Technical domain Stakeholders of the system are identified. • Stakeholder needs are prioritized • Critical performance measures are defined. (make sure it has a home in a content diagram somewhere in 3.x) • Stakeholder agreement that their needs and expectations are reflected adequately in the requirements is achieved. • Traceablity of stakeholder requirements to stakeholders and their needs is established • The system description, including system interfaces, functions and boundaries, for a system solution is defined. • System requirements (functional, performance, non-functional (e.g. logistics), and interface) and design constraints are defined. • Traceability of system requirements to operational requirements is developed. • MOPs References: [1] Section 6.4.2 Stakeholder needs and requirements definition process [1] Section 6.4.3 System requirements definition process [2] Section 6.4.2 Stakeholder needs and requirements definition process [2] Section 6.4.3 System requirements definition process [3] Section 17.3.3 Analyze System Requirements (pg. 441) [4] Chapter 7 Specify Spacecraft Requirements (pg. 57) (Functional)

### 1296.1: Includes engineering, logistics, program management, etc. (Functional)

### 1296.2: N/A (Functional)

### 1296.3: Purpose: Model mission activities, Identify system behaviors and functions, mission environment "Day in the life" use cases, examples, support, and maintenance to include: normal operations, off-nominal operations. This step defines work that has historicly been partially completed, but not necessarily always documented. This is critical to arriving at the complete system-level requirements. (Functional)

### 1296.4: Purpose: Analyze system and mission activities for constraints and critical properties. This analysis would be performed by technical domain stakeholders for each use case. Includes assessing which requirements are related to airworthiness, safety, mission effectiveness, suitability, etc. Output: Measure of Performance (MOP) (Functional)

### 1296.5: Purpose: Define the to-be context of the system by identifying the system interfaces and how it connects to the external systems for the mission scenarios and To-Be Domain. (Functional)

### 1296.6: Purpose: Identify design constraints imposed by the technical domain stakeholders (ex: engineering, logistics, etc), aquisition stakeholders (ex: programmatic constraints), statuatory requirements, regulatory requirements, etc. (Functional)

### 1296.7: Purpose: Utilize the outcomes of the preceding steps to generate the requirements specified at a black box level, a.k.a at the level of externally observable behavior (not HOW which is at the lower levls of the system definition). Include all attributes, system functions, performance and quality characteristics, required control, states, what the system must store (e.g. data, energy, & mass), interfaces, and system verification method(s). References: [3] 17.3.3 Analyze System Requirements; Specify black-box system requirements (pg 447) (Functional)

### 1296.8: Purpose: Define state machines to generate the composite behavior the system must perform based on the actions from all the scenarios in the prior steps. Includes when th system performs specific actions utilizing entry/exit conditions, triggers and guards, signal change events or time events. The state machines can be analyzed to identify state conflicts, etc., which then drives additional requirements and/or requirement clarifications (Functional)

### 1296.9: Purpose: Analyze requirements, activities, and state machines for potential failures which will then drive additional requirements and/or requirement clarifications. (Functional)

### 1296.10: Purpose: Analyze the risks involved with potential changes in requirements ex: performance margin, growth capacity, system variants,emerging threats, etc. References: [3] 17.3.3 Analyze System Requirements ; Analyze System Requirements Variation (pg. 453) (Functional)

### 1296.11: Purpose: A validation review with the acquisition stakeholders that the model is a correct representation of the acquisition stakeholder inputs. A validation review that the requirements and trade space align with the acquisition plan, acquisition strategy, and cost/schedule constraints. (Functional)

## 1297: 4.0 Define Logical Architecture Purpose • This activity is part of the system architecture design that includes decomposing the system into logical components that interact to satisfy the system requirements. The logical components are abstractions of the physical components that perform the system functionality without imposing implementation constraints. Prior to RFP, this step will be performed to the level needed for the system of interest under development. Within a system level, this may be repeated to evaluate alternate logical architectures to identify which architecture best covers the Reqts/MOEs/Etc without imposing artificial constraints. This step should be repeated as work progresses through each level of the system (e.g. system, sub-system, set, etc.). Input • The system description, including system interfaces, functions and boundaries, for a system solution is defined. • System requirements (functional, performance, non-functional (e.g. logistics), and interface) and design constraints are defined. • Legacy system functional interfaces Output • Logical Architecture • Functions and logical items traced to system requirements • Context, boundaries, and external interfaces of the system are defined. • Functional decomposition • Concepts, properties, characteristics, behaviors, functions, or constraints are allocated to the logical architecture • TPM References: [1] 6.4.4 Architecture Definition Process [2] 6.4.4 Architecture Definition Process [3] Section 17.3.4 Define Logical Architecture (pg. 454) [4] Chapter 8 Synthesize Alternative Architectures (pg 69) (Functional)

### 1297.1: Purpose: Decompose the system into logical items that interact to satisfy the system requirements without imposing implementation constraints. The system is decomposed into external interface items, application items to process each external input and output item flow, and infrastructure items to manage internal resources. Output: Identification of logical items (Functional)

### 1297.2: Purpose: Define interactions between logical items associated with each function. Output: Activities associated with each logical item (Functional)

### 1297.3: Purpose: Define the interconnections between the logical items. Output: Logical item interfaces (Functional)

### 1297.4: Purpose: Define and specify the features of each logical item. (Functional)

### 1297.5: Purpose: Define state machine for logical items dependent on input events and conditions. Output: State based requirements for the logical items (Functional)

## 1298: 5.0 Synthesize Candidate Physical Architectures Purpose • This activity synthesizes alternative physical architectures to satisfy the system requirements. The architecture is defined in terms of the physical components, the relationships, and their distribution across the architecture. The physical components of the system include hardware, software, persistent data, and operational procedures. Prior to RFP, this step will be performed to the level needed for the system of interest under development. This step should be repeated as work progresses through each level of the system (e.g. system, sub-system, set, etc.). Input • Logical Architecutre • System function definition • System requirements • System functional interface identification Output • Context, boundaries, and external interfaces of the system are defined. • Concepts, properties, characteristics, behaviors, functions, or constraints are allocated to physical entities. • System elements and their interfaces are identified. • Alignment of the architecture with requirements and design characteristics is achieved. • Traceability of physical elements to logical and system requirements is developed. • TPMs References [1] 6.4.4. Architecture Definition Process [2] 6.4.4. Architecture Definition Process [3] Section 17.3.5 Synthesize Candidate Physical Architecture [4] Chapter 8 Synthesize Alternative Architectures (pg 69) (Functional)

### 1298.1: Purpose: Establish criteria to partition functionality, persistent data, and control among the logical and physical components, and to partition the components among subsystems, nodes, and layers of the architecture. Output: Partitioning criteria References: [3] Section 17.3.5 Synthesize Candidate Physical Architectures; Define partitioning criteria (pg. 462) (Functional)

### 1298.2: Purpose: Aggregate logical items into logical groupings called logical nodes. A logical node represents an aggregation (or set) of logical items at a particular location. Output: Logical node definitions (Functional)

### 1298.3: Purpose: The logical items at a logical node are allocated to physical items at a physical node. (Functional)

### 1298.4: N/A (Functional)

### 1298.5: N/A (Functional)

### 1298.6: N/A (Functional)

### 1298.7: N/A (Functional)

### 1298.8: N/A (Functional)

### 1298.9: N/A (Functional)

### 1298.10: N/A (Functional)

## 1299: 6.0 Implementation & Integration Purpose: Implementation involves realization of specific system elements using appropriate technical specialites or disciplines (a.k.a detail design). Integration involves assembling the implemented system elements into a realized system that satisfies the system requirements, architecture and design. (Functional)

## 1300: 7.0 Verification & Validation Purpose: The purpose of verification is to verify that the system satisfies the requirements which is typically accomplished by a combination of inspection, analysis, demonstration, and test. The purpose of validation is to provide objective evidence that the system, when in use, fulfills its objectives and stakeholder requirements achieving its intended use in its intended operational environment. (Functional)

## 1301: 8.0 Preform System Analysis The aggregation of lower level analysis to perform system-level trade space analysis. This process informs decision making in the technical management process (Functional)

### 1301.1: N/A (Functional)

### 1301.2: N/A (Functional)

### 1301.3: N/A (Functional)

### 1301.4: N/A (Functional)

### 1301.5: N/A (Functional)

### 1301.6: N/A (Functional)

## 1302: 9.0 Manage Requirements Traceability Purpose: Capture text-based requirements, requirements relationships and rationale, and updates. (Functional)

### 1302.1: N/A (Functional)

### 1302.2: N/A (Functional)

### 1302.3: N/A (Functional)

### 1302.4: N/A (Functional)

### 1302.5: N/A (Functional)

## 1303: 10.0 Manage Technical Processes [1] Section 6.3: The Technical Management Processes are used to establish and evolve plans, to execute the plans, to assess actual achievements and progress against the plans and to control execution through to fulfillment. Individual Technical Management Processes may be invoked at any time in the life cycle and at any level The Technical Management Processes are used to establish and evolve plans, to execute the plans, to assess actual achievements and progress against the plans and to control execution through to fulfillment. Individual Technical Management Processes may be invoked at any time in the life cycle and at any level. The representation of results that drive management decisions. (Functional)

### 1303.1: Produce and coordinate effective and workable plans. [INCOSE HB 5.1.1.4] Inputs: Organization strategic plan, Source documents, Supply response, Project portfolio, Life cycle models, Project direction, Strategy documents, Project tailoring strategy, Project lessons learned, Documentation tree, QM corrective actions, Qualified personnel, Quality assurance plan Activities: Define the project, Plan project and technical management, Activate the project, Outputs: SEP, Model Development Plan, Project constraints, Project infrastructure needs, Project human resources needs, WBS, Project schedule, Project budget, Acquisition need, Project planning record, Schedule SET has an “Assist Team” available for program offices to use to start up modeling projects. Furthermore, the SET will also provide the Acquisition System Reference Model (ASRM) that could potentially be used as a template for program offices’ system models as well as a Stakeholder Analysis Model (SAM) that defines the stakeholders needs. Model Development Plan: The systems engineers may want to ask the following questions in their process of clarifying the modeling objectives to baseline expectation: Why is this effort being undertaken? What are the desired outputs for the project? What artifacts need to be produced by the model? What is the required timeframe for the model development effort? How much of the external environment needs to be modeled? Which behaviors (system, SoS, user, etc.) need to be modeled? What is the desired granularity of the model to support required analysis? What is the criteria for determining if the modeling process is complete? What interfaces to analysis tools? (Functional)

### 1303.2: Assess if the plans are aligned and feasible; determine the status of the project, technical and process performance; and direct execution to ensure that the performance is according to plans and schedules, within projected budgets, to satisfy technical objectives. [INCOSE HB 5.2.1.4] Inputs: WBS, Project budget, Project schedule, Procedure, Reports, Configuration baselines, Information repository, Measurement repository, QM corrective actions, Quality assurance evaluation report, Validated requirements Activities: Plan for project assessment and control, Assess the project, Control the project Outputs: Project assessment and control strategy, Project performance measures needs, Project performance measures data, Project status report, Project control requests, Project change requests, Project lessons learned, Project assessment and control record (Functional)

### 1303.3: Provide a structured, analytical framework for objectively identifying, characterizing and evaluating a set of alternatives. This includes selecting and recording the most beneficial course of action. [INCOSE HB 5.3.1.4] Inputs: Decision situation Activities: Prepare for decisions, Analyze the decision information, Make and manage decisions Outputs: Decision management process, Decision report, Decision record (Functional)

### 1303.4: Identify, analyze, treat and monitor the risks continually. [INCOSE HB 5.4.1.4] Inputs: Candidate risk and opportunities Activities: Plan risk management, Manage the risk profile, Analyze risks, Treat risks, Monitor risks Outputs: Risk management strategy, Risk report, Risk record (Functional)

### 1303.5: Manage and control system elements and configurations over the life cycle. CM also manages consistency between a product and its associated configuration definition. [INCOSE HB 5.5.1.4] Inputs: Candidate configuration items, Project change requests Activities: Plan configuration management (includes model governance), Perform configuration identification, Perform configuration change management, Perform configuration status accounting, Perform configuration evaluation, Perform model configuration management, Perform release control, Perform model release control Outputs: Configuration management strategy, Configuration baselines, Configuration management report, Configuration management record (Functional)

### 1303.6: Includes controlling interface between various models/simulations (other system models and things like aero perf models, etc) - includes Model ICD, etc. Inputs: model change requests Activities: Perform model configuration management, , Perform Model release control Outputs: Configuration management strategy, Configuration baselines, Configuration management report, Configuration management record (Functional)

### 1303.7: Generate, obtain, confirm, transform, retain, retrieve, disseminate and dispose of information, to designated stakeholders. [INCOSE HB 5.6.1.4] Inputs: Candidate information items, Project change requests Activities: Prepare for information management, Perform information management, Manage style guides, Manage schema, Manage profiles, Manage views Outputs: Information management strategy, Information repository, Information management report, Information management record, Style guides, Schema, Profiles, Views (Functional)

### 1303.8: Collect and report objective data and information to support effective management and demonstrate the quality of the products, services, and processes. [INCOSE HB 5.7.1.4] Inputs: Measurement needs, Measurement data Activities: Prepare for measurement, Perform measurement, Define model measurements Outputs: Measurement strategy, Measurement repository, Measurement report, Measurement record (Functional)

### 1303.9: Ensure the effective application of the organization’s Quality Management process to the project. [INCOSE HB 5.8.1.4] Inputs: Quality management guidelines, Quality management plan, Quality management report, Quality management corrective actions Activities: Prepare for quality assurance, Perform product or service evaluations, Perform process evaluations, Manage QA records and reports, Treat incidents and problems Outputs: Quality assurance plan, Quality assurance report, Quality assurance evaluation report, Quality assurance record (Functional)

## 1304: 11.0 Finalize RFP Input Purpose: Finalize products for RFP release Output: System Specification Package, SOW, CM Plan, SEP, WBS, CDRL, Evaluation Factors, etc. (Functional)

### 1304.1: N/A (Functional)

### 1304.2: N/A (Functional)

### 1304.3: N/A (Functional)

### 1304.4: N/A (Functional)

### 1304.5: N/A (Functional)

## 1433: The UAV shall complete an autonomous deck landing without utilizing its RAST arresting gear, if sea conditions permit. (Functional)

## 1435: The UAV shall be landed on ship using manual control in the event that UCARS fails. (Functional)

## 1434: The UAV shall autonomously back away from ship to a safe distance in the event that UCARS fails during landing operations. (Functional)

## 1436: An operator shall verify that the lost personnel are present in the camera images or video transmitted from the UAV to ship. (Functional)

## 1437: The video link from the UAV to ship shall be easily reestablished in the event of temporary loss of signal. (Functional)

## 1438: The UAV shall reset its communication equipment in the event of a software failure. (Functional)

## 1439: If possible, the UAV shall loiter about an area when hovering is not possible. (Functional)

## 1449: The UAV shall be able to complete a specified example mission scenario (Functional)
